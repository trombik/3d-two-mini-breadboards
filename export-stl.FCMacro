# -*- coding: utf-8 -*-

import FreeCAD
import Mesh

FreeCAD.open(u"src/two-mini-breadboards.FCStd")
__objs__=[]
__objs__.append(FreeCAD.getDocument("two_mini_breadboards").getObject("Cut"))
Mesh.export(__objs__,u"two-mini-breadboards.stl")

del __objs__
